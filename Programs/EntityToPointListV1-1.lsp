;; Entity to Point List  -  Lee Mac
;; Returns a list of points describing or approximating the supplied entity, else nil if the entity is not supported.
;; ent - [ent] Entity name to be described by point list (POINT/LINE/ARC/CIRCLE/LWPOLYLINE/POLYLINE/ELLIPSE/SPLINE)
;; acc - [num] Positive number determining the point density for non-linear objects

(defun LM:ent->pts ( ent acc / der di1 di2 enx inc lst par rad )
    (setq enx (entget ent))
    (cond
        (   (= "POINT" (cdr (assoc 0 enx)))
            (list (cdr (assoc 10 enx)))
        )
        (   (= "LINE" (cdr (assoc 0 enx)))
            (list (cdr (assoc 10 enx)) (cdr (assoc 11 enx)))
        )
        (   (wcmatch (cdr (assoc 0 enx)) "ARC,CIRCLE")
            (setq di1 0.0
                  di2 (vlax-curve-getdistatparam ent (vlax-curve-getendparam ent))
                  inc (/ di2 (1+ (fix (* acc (/ di2 (cdr (assoc 40 enx)) (+ pi pi))))))
                  di2 (- di2 1e-8)
            )
            (while (< di1 di2)
                (setq lst (cons (vlax-curve-getpointatdist ent di1) lst)
                      di1 (+ di1 inc)
                )
            )
            (reverse (if (vlax-curve-isclosed ent) lst (cons (vlax-curve-getendpoint ent) lst)))
        )
        (   (and (wcmatch (cdr (assoc 0 enx)) "*POLYLINE") (zerop (logand 80 (cdr (assoc 70 enx)))))
            (setq par 0)
            (repeat (fix (+ 1.0 1e-8 (vlax-curve-getendparam ent)))
                (cond
                    (   (not (setq der (vlax-curve-getsecondderiv ent par))))
                    (   (equal der '(0.0 0.0 0.0) 1e-8)
                        (setq lst (cons (vlax-curve-getpointatparam ent par) lst))
                    )
                    (   (setq rad (distance '(0.0 0.0) (vlax-curve-getfirstderiv ent par))
                              di1 (vlax-curve-getdistatparam ent par)
                              di2 (vlax-curve-getdistatparam ent (1+ par))
                        )
                        (setq inc (/ (- di2 di1) (1+ (fix (* acc (/ (- di2 di1) rad (+ pi pi))))))
                              di2 (- di2 1e-8)
                        )
                        (while (< di1 di2)
                            (setq lst (cons (vlax-curve-getpointatdist ent di1) lst)
                                  di1 (+ di1 inc)
                            )
                        )
                    )
                )
                (setq par (1+ par))
            )
            (setq lst (cons (vlax-curve-getendpoint ent) lst))
            (while
                (and (cdr lst)
                     (or (equal (car lst) (last lst) 1e-8)
                         (equal (car lst) (cadr lst) 1e-8)
                     )
                )
                (setq lst (cdr lst))
            )
            (reverse lst)
        )
        (   (= "ELLIPSE" (cdr (assoc 0 enx)))
            (setq di1 (vlax-curve-getdistatparam ent (vlax-curve-getstartparam ent))
                  di2 (vlax-curve-getdistatparam ent (vlax-curve-getendparam   ent))
                  di2 (- di2 1e-8)
            )
            (while (< di1 di2)
                (setq lst (cons (vlax-curve-getpointatdist ent di1) lst)
                      rad (distance '(0.0 0.0) (vlax-curve-getfirstderiv ent (vlax-curve-getparamatdist ent di1)))
                      di1 (+ di1 (/ di2 (1+ (fix (* acc (/ di2 rad (+ pi pi)))))))
                )
            )
            (reverse (if (vlax-curve-isclosed ent) lst (cons (vlax-curve-getendpoint ent) lst)))
        )
        (   (= "SPLINE" (cdr (assoc 0 enx)))
            (setq di1 (vlax-curve-getdistatparam ent (vlax-curve-getstartparam ent))
                  di2 (vlax-curve-getdistatparam ent (vlax-curve-getendparam   ent))
                  inc (/ di2 acc)
                  di2 (- di2 1e-8)
            )
            (while (< di1 di2)
                (setq lst (cons (vlax-curve-getpointatdist ent di1) lst)
                      der (/ (distance '(0.0 0.0) (vlax-curve-getsecondderiv ent (vlax-curve-getparamatdist ent di1))) inc)
                      di1 (+ di1 (if (equal 0.0 der 1e-10) inc (max (/ 1.0 der (* acc inc)) inc)))
                )
            )
            (reverse (if (vlax-curve-isclosed ent) lst (cons (vlax-curve-getendpoint ent) lst)))
        )
    )
)
